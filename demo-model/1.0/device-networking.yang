module device-networking {
  yang-version 1.1;
  namespace "urn:demo:device-networking";
  prefix dn;

  import ietf-inet-types {
    prefix inet;
  }

  organization
    "kubenet";
  description
    "Small demo model with a few clear must validations.";

  revision "2025-08-25" {
    description
      "Initial simple demo.";
  }

  container network {
    description
      "Top-level container holding all interfaces and services.";

    list interface {
      key "name";
      description
        "Interface list.";

      leaf name {
        type string;
      }

      leaf type {
        type enumeration {
          enum ethernet;
          enum loopback;
        }
        mandatory true;
      }

      leaf admin-up {
        type boolean;
        default "false";
      }

      leaf speed {
        type enumeration {
          enum "1G";
          enum "10G";
        }
        description
          "Only meaningful for ethernet.";
        /* If ethernet, speed must be set */
        must "not(../type = 'ethernet') or boolean(.)" {
          error-message
            "Ethernet interfaces must have a speed set.";
        }
      }

      leaf ipv4-enabled {
        type boolean;
        default "false";
      }

      leaf-list ipv4-address {
        type inet:ipv4-address;
        description
          "IPv4 addresses on the interface.";
      }

      /* If IPv4 enabled, require at least one address */
      must "not((./ipv4-enabled = 'true') and (count(./ipv4-address) = 0))" {
        error-message
          "Enable IPv4 only if at least one IPv4 address is configured.";
      }

      must " not(./type = 'ethernet') or
    ( (./speed = '1G'  and
         sum(/dn:network/dn:service[dn:if-name = current()/dn:name]/dn:bandwidth) <= 1000)
      or
      (./speed = '10G' and
         sum(/dn:network/dn:service[dn:if-name = current()/dn:name]/dn:bandwidth) <= 10000) )" {
        error-message
          "Total service bandwidth on this interface exceeds its capacity.";
      }
    }

    list service {
      key "name";
      description
        "Service that binds to an interface and reserves bandwidth.";

      leaf name {
        type string;
      }

      leaf if-name {
        type leafref {
          path "/dn:network/dn:interface/dn:name";
        }
        mandatory true;
      }

      leaf bandwidth {
        type uint32;
        units "Mbps";
        mandatory true;
      }
    }
  }
}
